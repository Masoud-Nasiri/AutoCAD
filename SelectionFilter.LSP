(progn
  (princ "\nSelectionFilter v2.0 by Masoud Nasiri, 6 November, 2020 @ Copyleft. All wrongs resered.")
  (princ))

(defun c:selectionFilter ()
  (defun-q *error* (messageError)(princ))
  (firstList))

(defun-q firstList (/ filterType)
  (initget "l L p P a A c C s S b B h H t T m M d D 3d 3D r R o O")
  (setq filterType (getkword "\nEnter entity type <Other>:[Line/Polyline/Arc/Circle/Spline/Block Reference/Hatch/Text/Mtext/Dimension/3D Solid/Region/Other]"))
  (if (or (= filterType nil) (= filterType "O"))
    (secondList)
    (filterFunction T filterType)
  ))

(defun-q secondList (/ filterType)
  (initget "r R x X m M 3d 3D h H e E p P w W l L s S i I b B")
  (setq filterType (getkword "\nEnter entity type <Back>:[Ray/Xline/Mline/3D Polyline/Helix/Ellipse/Point/Wipeout/Leader/Solid/Image/Back]"))
  (if (or (= filterType nil) (= filterType "B"))
    (firstList)
    (filterFunction nil filterType)
  ))

(defun-q filterFunction (mainMenu filterType / selectionSet)
  (if mainMenu
    (cond
      ((= (strcase filterType) "A")  (setq filterType "ARC"))
      ((= (strcase filterType) "B")  (setq filterType "INSERT"))
      ((= (strcase filterType) "C")  (setq filterType "CIRCLE"))
      ((= (strcase filterType) "D")  (setq filterType "DIMENSION"))
      ((= (strcase filterType) "H")  (setq filterType "HATCH"))
      ((= (strcase filterType) "L")  (setq filterType "LINE"))
      ((= (strcase filterType) "M")  (setq filterType "MTEXT"))
      ((= (strcase filterType) "P")  (setq filterType "LWPOLYLINE"))
      ((= (strcase filterType) "R")  (setq filterType "REGION"))
      ((= (strcase filterType) "S")  (setq filterType "SPLINE"))
      ((= (strcase filterType) "T")  (setq filterType "TEXT"))
      ((= (strcase filterType) "3D") (setq filterType "3DSOLID")))
    (cond
      ((= (strcase filterType) "E")  (setq filterType "ELLIPSE"))
      ((= (strcase filterType) "H")  (setq filterType "HELIX"))
      ((= (strcase filterType) "I")  (setq filterType "IMAGE"))
      ((= (strcase filterType) "L")  (setq filterType "LEADER"))
      ((= (strcase filterType) "M")  (setq filterType "MLINE"))
      ((= (strcase filterType) "P")  (setq filterType "POINT"))
      ((= (strcase filterType) "R")  (setq filterType "RAY"))
      ((= (strcase filterType) "S")  (setq filterType "Solid"))
      ((= (strcase filterType) "X")  (setq filterType "XLINE"))
      ((= (strcase filterType) "W")  (setq filterType "WIPEOUT"))
      ((= (strcase filterType) "3D") (setq filterType "POLYLINE"))))
  (setq selectionSet (cadr (ssgetfirst)))
  (if selectionSet
    (progn
      (command "_.select" selectionSet "")
      (sssetfirst nil (ssget "P" (list (cons 0 filterType)))))
    (sssetfirst nil (ssget (list (cons 0 filterType)))))
  (princ))
